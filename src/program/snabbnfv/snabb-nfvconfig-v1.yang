module snabb-nfvconfig-v1 {
  namespace "http://snabb.co/nfvconfig-v1";
  prefix snabb-nfvconfig-v1;

  import ietf-yang-types { prefix yang; }
  import ietf-inet-types { prefix inet; }

  organization "Snabb";
  contact "snabb-devel@googlegroups.com";

  description
    "This module describes the configuration of SnabbNFV.";

  revision "2016-10-27" {
    description
     "Initial version that reflects Snabb Switch 2016.11 “Babaco”.";
    reference
      "https://github.com/snabbco/snabb/releases/tag/v2016.11";
  }

  typedef pcap-filter {
    type string;
    description "A pcap-filter(7) expression.";
  }

  typedef gbps {
    type decimal64 {
      fraction-digits 4;
      range "0..max";
    }

    description "Gigabits per second.";
  }

  identity tunnel-type {
    description "Base identity from which all tunnel types are derived.";
  }

  identity L2TPv3 {
    base "tunnel-type";
    description "Layer 2 Tunneling Protocol Version 3";
  }

  identity crypto-type {
    description
      "Base identity from which all transport cryptography types are derived.";
  }

  identity esp-aes-128-gcm {
    base "crypto-type";
    description
      "Encapsulating Security Payload using AES 128 in Galois Counter Mode";
  }

  typedef hexstring4 {
    type "string" {
      pattern "[0-9a-fA-F]{8}";
    }
    description "Four bytes encoded as a hexadecimal string.";
  }

  typedef hexstring8 {
    type "string" {
      pattern "[0-9a-fA-F]{16}";
    }
    description "Eight bytes encoded as a hexadecimal string.";
  }

  typedef hexstring16 {
    type "string" {
      pattern "[0-9a-fA-F]{32}";
    }
    description "Sixteen bytes encoded as a hexadecimal string.";
  }

  list port {
    key port_id;
    description
      "An entry containing configuration information applicable to a particular
    virtual port.";

    leaf port_id {
      type string;
      mandatory true;
      description "The unique identifier of the port.";
    }

    leaf mac_address {
      type yang:mac-address;
      mandatory true;
      description "MAC address of the port.";
    }

    leaf vlan {
      type uint16 {
        range "0..4095";
      }
      description "Vlan tag.";
    }

    leaf ingress_filter {
      type pcap-filter;
      description "Ingress traffic filtering rules.";
    }

    leaf egress_filter {
      type pcap-filter;
      description "Egress traffic filtering rules.";
    }

    container tunnel {
      description "L2TPv3 tunnel configuration.";

      leaf type {
        type identityref {
          base "tunnel-type";
        }
        mandatory true;
        description
          "Tunnel type identifier.";
      }

      leaf local_cookie {
        type hexstring8;
        mandatory true;
        description "Local cookie";
      }

      leaf remote_cookie {
        type hexstring8;
        mandatory true;
        description "Remote cookie";
      }

      leaf next_hop {
        type yang:mac-address;
        description "Gateway MAC address.";
      }

      leaf local_ip {
        type inet:ipv6-address-no-zone;
        mandatory true;
        description "Local IPv6 address.";
      }

      leaf remote_ip {
        type inet:ipv6-address-no-zone;
        mandatory true;
        description "Remote IPv6 address.";
      }

      leaf session {
        type int32;
        description
          "The session field of the L2TPv3 header will be overwritten with this
        value.";
      }
    }

    leaf rx_police {
      type gbps;
      description "Allowed input rate in Gigabits per second.";
    }

    leaf tx_police {
      type gbps;
      description "Allowed output rate in Gigabits per second.";
    }

    container crypto {
      description "Transport cryptography configuration.";

      leaf type {
        type identityref {
          base "crypto-type";
        }
        mandatory true;
        description
          "Cryptography type identifier.";
      }

      leaf spi {
        type uint32 {
          range "256..max";
        }
        mandatory true;
        description
          "“Security Parameters Index” as specified in RFC 4303.";
      }

      leaf transmit_key {
        type hexstring16;
        mandatory true;
        description
          "128-bit AES key as specified in RFC 4106 used for the encryption of
        outgoing packets.";
      }

      leaf transmit_salt {
        type hexstring4;
        mandatory true;
        description
          "Salt as specified in RFC 4106 used for the encryption of outgoing
        packets.";
      }

      leaf receive_key {
        type hexstring16;
        mandatory true;
        description
          "128-bit AES key as specified in RFC 4106 used for the decryption of
        incoming packets.";
      }

      leaf receive_salt {
        type hexstring4;
        mandatory true;
        description
          "Salt as specified in RFC 4106 used for the decryption of incoming
        packets.";
      }

      leaf auditing {
        type boolean;
        default false;
        description
          "Indicates whether to enable or disable “Auditing” as specified in
        RFC 4303. The default is no auditing.";
      }
    }
  }
}
